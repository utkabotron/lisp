;;; Инструменты для работы с атрибутами блоков
;;; Команды: SetAttFromText, AttToZMulti

;;; SetAttFromText - Установка значения атрибута из текста
(defun c:SetAttFromText ( / blk ss e ent attName txtEnt txtVal updated)
  (setq attName "HEIGHT")
  (princ "\nSelect a block reference (INSERT): ")
  (setq blk (car (entsel)))
  (if (not blk)
    (progn (princ "\nNo block selected!") (exit))
  )
  (if (/= (cdr (assoc 0 (entget blk))) "INSERT")
    (progn (princ "\nSelected object is not a block reference!") (exit))
  )
  (princ "\nSelect a TEXT or MTEXT object: ")
  (setq txtEnt (car (entsel)))
  (if (not txtEnt)
    (progn (princ "\nNo text selected!") (exit))
  )
  (setq typ (cdr (assoc 0 (entget txtEnt))))
  (if (and (/= typ "TEXT") (/= typ "MTEXT"))
    (progn (princ "\nSelected object is not TEXT or MTEXT!") (exit))
  )
  (setq txtVal (cdr (assoc 1 (entget txtEnt))))
  (setq updated nil)
  ;; Loop through all entities in the block (attributes are children of INSERT)
  (setq e (entnext blk))
  (while e
    (setq ent (entget e))
    (if (and (= (cdr (assoc 0 ent)) "ATTRIB")
             (= (strcase (cdr (assoc 2 ent))) (strcase attName)))
      (progn
        (entmod (subst (cons 1 txtVal) (assoc 1 ent) ent))
        (entupd e)
        (setq updated T)
      )
    )
    ;; break if end of block sequence
    (if (= (cdr (assoc 0 ent)) "SEQEND")
      (setq e nil)
      (setq e (entnext e))
    )
  )
  (if updated
    (princ (strcat "\nAttribute " attName " updated to: " txtVal))
    (princ (strcat "\nAttribute " attName " not found in this block!"))
  )
  (princ)
)

;;; AttToZMulti - Установка Z-координаты блоков из атрибута HEIGHT
(defun c:AttToZMulti ( / ss cnt attName i blk ent attVal zVal data insPt newInsPt updated)
  ;; Set attribute tag to use
  (setq attName "HEIGHT")
  (princ "\nSelect block references (INSERT): ")
  (setq ss (ssget '((0 . "INSERT"))))
  (if (not ss)
    (progn (princ "\nNo blocks selected!") (exit))
  )
  (setq cnt (sslength ss))
  (setq updated 0)
  (setq i 0)
  (while (< i cnt)
    (setq blk (ssname ss i))
    ;; Search for attribute HEIGHT
    (setq attVal nil)
    (setq e (entnext blk))
    (while e
      (setq ent (entget e))
      (if (and (= (cdr (assoc 0 ent)) "ATTRIB")
               (= (strcase (cdr (assoc 2 ent))) (strcase attName)))
        (setq attVal (cdr (assoc 1 ent)))
      )
      (if (= (cdr (assoc 0 ent)) "SEQEND")
        (setq e nil)
        (setq e (entnext e))
      )
    )
    (if attVal
      (progn
        ;; Convert to number (support decimal comma and point)
        (setq zVal (distof attVal 2))
        (if (null zVal)
          (setq zVal (distof (vl-string-subst "." "," attVal) 2))
        )
        (if zVal
          (progn
            ;; Update block position Z
            (setq data (entget blk))
            (setq insPt (cdr (assoc 10 data)))
            (setq newInsPt (list (nth 0 insPt) (nth 1 insPt) zVal))
            (entmod (subst (cons 10 newInsPt) (assoc 10 data) data))
            (entupd blk)
            (setq updated (1+ updated))
            (princ (strcat "\nBlock #" (itoa (1+ i)) " updated: Z = " (rtos zVal 2 3)))
          )
          (princ (strcat "\nBlock #" (itoa (1+ i)) ": cannot convert '" attVal "' to number!"))
        )
      )
      (princ (strcat "\nBlock #" (itoa (1+ i)) ": attribute " attName " not found!"))
    )
    (setq i (1+ i))
  )
  (princ (strcat "\nTotal blocks updated: " (itoa updated)))
  (princ)
)

(princ "\nAttribute tools loaded: SetAttFromText, AttToZMulti")
(princ)
